module test {

  yang-version "1";

  // namespace
  namespace "http://psefabric/policy";

  prefix "policy";

  leaf-list test-aggregation {
	  type leafref {
		  path "/level1/level2";
	  }
  }
  
  list level1 {
	  key level1-name;
	  leaf level1-name {
		  type string;
		  } 
	  leaf-list level2 {
		  type string;
		  }
	  }
   }
