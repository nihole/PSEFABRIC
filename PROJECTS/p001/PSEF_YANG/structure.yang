// p001

module structure {

  yang-version "1.1";

  // namespace
  namespace "http://psefabric/structure";

  prefix "structure";

  import psefabric-types { prefix types; }
  
  container structure {
	  leaf-list data-centers {
		  type types:dc;
	  }
	  leaf-list VRFs {
		  type types:vrf;
	  }
	  leaf-list zones {
		  type types:zone;
	  }
	  leaf-list equipment {
		  type types:eq;
	  }
	  leaf-list  interfaces {
		  type types:interface;
	  }	  
	  list vlans {
		  key vlan-name;
		  leaf vlan-name {
			  type string;
		  }
		  leaf vlan-number {
			  type int16 {
			  range "0..4095";  
			  }
		  }
	  }
  }
}
