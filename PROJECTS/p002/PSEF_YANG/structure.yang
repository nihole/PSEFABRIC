// p002

module structure {
  yang-version "1.1";

  // namespace
  namespace "http://psefabric/structure";

  prefix "structure";

  import psefabric-types { prefix types; }
  
  container structure {
	  leaf-list data-center {
		  type types:dc;
	  }
	  leaf-list area {
		  type types:area;
	  }
	  leaf-list zone {
		  type types:zone;
	  }
	  leaf-list sub-zone {
		  type types:sub-zone;
	  }
	  list vlans {
		  key vlan-name;
		  leaf vlan-name {
			  type string;
		  }
		  leaf vlan-number {
			  type int16 {
			  range "0..4095";  
			  }
		  }
	  }
  }
}
