// p002

submodule services {
  belongs-to policy {
    prefix policy;
  }
	  
  yang-version "1.1";

  import ietf-inet-types { prefix ietf; }
  import ietf-packet-fields { prefix fields; }
  
  list services {
	  key service-name;
	  leaf service-name {
		  mandatory true;
		  type string;
	  }
	  container parameters {
		  leaf pa-service-name {
			  type string;
			  default '';
		  }
		  leaf aci-filter-name {
			  type string;
			  default '';
		  }
		  leaf configure-svc {
//			  mandatory true;
			  type boolean;
			  default 'false';
		  }  
	  }
	  leaf prot {
		  type int8;
		  description
			  "Protocol number";
	  }
	  container ports {
		  container source-port-range {
		      presence "Enables setting source port range";
		      description
		        "Inclusive range representing source ports to be used.
		        When only lower-port is present, it represents a single port.";
		      leaf lower-port {
		        type int16;
		        mandatory true;
		        description
		          "Lower boundary for port.";
		      }
		      leaf upper-port {
		        type int16;
		        must ". >= ../lower-port" {
		          error-message
		          "The upper-port must be greater than or equal to lower-port";
		        }
		        description
		          "Upper boundary for port . If existing, the upper port
		          must be greater or equal to lower-port.";
		      }
		    }
		    container destination-port-range {
		      presence "Enables setting destination port range";
		      description
		        "Inclusive range representing destination ports to be used. When
		        only lower-port is present, it represents a single port.";
		      leaf lower-port {
		        type int16;
		        mandatory true;
		        description
		          "Lower boundary for port.";
		      }
		      leaf upper-port {
		        type int16;
		        must ". >= ../lower-port" {
		          error-message
		            "The upper-port must be greater than or equal to lower-port";
		        }

		        description
		          "Upper boundary for port. If existing, the upper port must
		          be greater or equal to lower-port";
		      }
		    }
	  }
   }
  list service-sets {
	 key service-set-name;
	 leaf service-set-name {
		 mandatory true;
		  type string;
	  }
	 container parameters {
		 leaf pa-service-grp-name {
			  type string;
			  default '';
		  }
		  leaf aci-subject-name {
			  type string;
			  default '';
		  }
		 leaf configure-svcset {
//			 mandatory true;
			 default 'false';
			  type boolean;
		  } 
	 }
	  leaf-list services {
          min-elements 1;
		  type leafref {
			  path "/services/service-name";
		  }
	 }
	  
 }
}
