module psefabric-types {

  yang-version "1";

  // namespace
  namespace "http://psefabric/types";

  prefix "types";

  import ietf-inet-types { prefix inettypes; }
 
  typedef str_1 {
	  type string;
  }
  typedef str_2 {
	  type string;
  }
  typedef str_3 {
	  type string;
  }
  typedef str_4 {
	  type string;
  }
  typedef str_5 {
	  type string;
  }
  typedef str_6 {
	  type string;
  }
  typedef str_7 {
      type string;
  }
  typedef str_8 {
      type string;
  }
  typedef str_9 {
      type string;
  }
}
