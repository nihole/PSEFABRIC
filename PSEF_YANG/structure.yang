module structure {

  yang-version "1";

  // namespace
  namespace "http://psefabric/structure";

  prefix "structure";

  import psefabric-types { prefix types; }
  
  container structure {
	  leaf-list str_1 {
		  type types:str_1;
	  }
	  leaf-list str_2 {
		  type types:str_2;
	  }
	  leaf-list str_3 {
		  type types:str_3;
	  }
	  leaf-list str_4 {
		  type types:str_4;
	  }
	  leaf-list str_5 {
		  type types:str_5;
	  }
	  leaf-list str_6 {
		  type types:str_6;
	  }		
	  leaf-list str_7 {
		  type types:str_7;
	  }
	  leaf-list str_8 {
		  type types:str_8;
	  }
	  leaf-list str_9 {
		  type types:str_9;
	  }
	  list vlans {
		  key vlan-name;
		  leaf vlan-name {
			  type string;
		  }
		  leaf vlan-number {
			  type int16 {
			  range "0..4095";  
			  }
		  }
	  }
  }
}
