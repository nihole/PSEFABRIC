submodule addresses {

  yang-version "1";
  belongs-to policy {
	  prefix policy;
  }

  import ietf-inet-types { prefix ietf; }
  import structure { prefix structure; }
  
  
  list addresses {
	  key address-name;
	  leaf address-name {
		  mandatory true;
		  type string;
	  }
	  leaf ipv4-prefix {
		  mandatory true;
		  type ietf:ipv4-prefix;
		  description
			  "ipv4 prefix";
  	  }
	  container parameters {
		  leaf addr_par_1 {
//			  mandatory true;
			  default false;
			  type boolean;
		  }
		  leaf addr_par_2 {
//			  mandatory true;
			  default false;
			  type boolean;
		  }
		  leaf addr_par_3 {
			  type string;
//			  mandatory true;
			  default '';
		  }
		  leaf addr_par_4 {
			  type string;
//			  mandatory true;
			  default '';
		  }
		  leaf addr_par_5 {
			  type string;
//			  mandatory true;
			  default '';
		  }
		  leaf addr_par_6 {
			  type string;
//			  mandatory true;
			  default '';
		  }
	  }
	  container structure {
		  leaf str_1 {
			  type leafref {
				  path "/structure:structure/structure:str_1";
			  }
			  mandatory true;
		  }
		  leaf str_2 {
			  type leafref {
				  path "/structure:structure/structure:str_2";
			  }
			  mandatory true;
		  }
		  leaf str_3 {
			  type leafref {
				  path "/structure:structure/structure:str_3";
			  }
//			  mandatory true;
		  }
		  leaf str_4 {
			  type leafref {
				  path "/structure:structure/structure:str_4";
			  }
//			  mandatory true;
		  }
		  leaf str_5 {
			  type leafref {
				  path "/structure:structure/structure:str_5";
			  }
//			  mandatory true;
		  }
		  leaf str_6 {
			  type leafref {
				  path "/structure:structure/structure:str_6";
			  }
//			  mandatory true;
		  }
		  leaf str_7 {
			  type leafref {
				  path "/structure:structure/structure:str_7";
			  }
//			  mandatory true;
		  }
		  leaf str_8 {
			  type leafref {
				  path "/structure:structure/structure:str_8";
			  }
//			  mandatory true;
		  }
		  leaf str_9 {
			  type leafref {
				  path "/structure:structure/structure:str_9";
			  }
//			  mandatory true;
		  }
		  leaf vlan {
			  type leafref {
				  path "/structure:structure/structure:vlans/structure:vlan-number";
			  }
//			  mandatory false;
		  }
	  }

  }
  
  list address-sets {
	  key address-set-name;
	  leaf address-set-name {
		  mandatory true;
		  type string;
	  }
	  container parameters {
		  leaf addrset_par_1 {
//			  mandatory true;
			  default false;
			  type boolean;
		  }
		  leaf addrset_par_2 {
//			  mandatory true;
			  default false;
			  type boolean;  
		  }
		  leaf addrset_par_3 {
			  type string;
			  default '';
		  }
		  leaf addrset_par_4 {
			  type string;
			  default '';
//			  mandatory true;
		  }
		  leaf addrset_par_5 {
			  type string;
			  default '';
//			  mandatory true;
		  }
		  leaf addrset_par_6 {
			  type string;
			  default '';
//			  mandatory true;
		  }
	  }
 	  leaf-list addresses {
 		  min-elements 1;
		  type leafref {
			  path "/addresses/address-name";
		  }
      }
	  
  }
  
}
