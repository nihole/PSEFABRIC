submodule applications {
  belongs-to policy {
    prefix policy;
  }
	  
  yang-version "1";

  import ietf-inet-types { prefix ietf; }
  import ietf-packet-fields { prefix fields; }
  
  list applications {
	  key application-name;
	  leaf application-name {
		  mandatory true;
		  type string;
	  }
	  container parameters {
		  leaf app_par_1 {
//			  mandatory true;
			  default false;
			  type boolean;
		  }
		  leaf app_par_2 {
//			  mandatory true;
			  default false;
			  type boolean;
		  }
		  leaf app_par_3 {
			  type string;
			  default '';
		  }
		  leaf app_par_4 {
			  type string;
			  default '';
		  }
		  leaf app_par_5 {
			  type string;
			  default '';
		  }
		  leaf app_par_6 {
			  type string;
			  default '';
		  }
	  }
   }
  list application-sets {
	 key application-set-name;
	 leaf application-set-name {
		 mandatory true;
		  type string;
	  }
	  container parameters {
		  leaf appset_par_1 {
//			  mandatory true;
			  default false;
			  type boolean;
		  }
		  leaf appset_par_2 {
//			  mandatory true;
			  default false;
			  type boolean;
		  }
		  leaf appset_par_3 {
			  type string;
			  default '';
		  }
		  leaf appset_par_4 {
			  type string;
			  default '';
		  }
		  leaf appset_par_5 {
			  type string;
			  default '';
		  }
		  leaf appset_par_6 {
			  type string;
			  default '';
		  }
	  }
	  leaf-list applications {
          min-elements 1;
		  type leafref {
			  path "/applications/application-name";
		  }
	 }
	  
 }
}
