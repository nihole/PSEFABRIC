module policy {

  yang-version "1";

  // namespace
  namespace "http://psefabric/policy";

  prefix "policy";

  include addresses;
  include services;
  include applications;
  
  list policies {
	  key policy-name;
		  leaf policy-name {
			  type string;
			  mandatory true;
		  }
		  container parameters {
			  leaf plc_par_1 {
//				  mandatory true;
				  default false;
				  type boolean;  
			  }
			  leaf plc_par_2 {
//				  mandatory true;
				  default false;
				  type boolean;  
			  }
			  leaf plc_par_3 {
				  type string;
				  default '';
			  }
			  leaf plc_par_4 {
				  type string;
				  default '';
			  }
			  leaf plc_par_5 {
				  type string;
				  default '';
			  }
			  leaf plc_par_6 {
				  type string;
				  default '';
			  }
		  }
		  container match {
			  leaf-list source-address-sets {
				  min-elements 1;
				  type leafref {
					  path "/address-sets/address-set-name";
				  }
			   }
			  leaf-list destination-address-sets {
				  min-elements 1;
				  type leafref {
					  path "/address-sets/address-set-name";
				  }
			  }  
			  leaf-list service-sets {
				  min-elements 1;
				  type leafref {
					  path "/service-sets/service-set-name";
				  }
			  }
			  leaf-list application-sets {
				  min-elements 1;
				  type leafref {
					  path "/application-sets/application-set-name";
				  }
			  }
		  }
		  container then {
              description
                "Definitions of action criteria for this Access List Entry.";
              choice packet-handling {
                default "permit";
                description
                  "Packet handling action.";
                case deny {
                  leaf deny {
                    type empty;
                    description
                      "Deny action.";
                  }
                }
                case permit {
                  leaf permit {
                    type empty;
                    description
                      "Permit action.";
                  }
               }
           }
	  }    
   }

}
