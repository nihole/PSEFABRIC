module psefabric-types {

  yang-version "1";

  // namespace
  namespace "http://psefabric/types";

  prefix "types";

  import ietf-inet-types { prefix inettypes; }
 
  typedef dc {
	  type string;
  }
  typedef eq {
	  type inettypes:host;
  }
  typedef interface {
	  type string;
  }
  typedef zone {
	  type string;
  }
  typedef vrf {
	  type string;
  }
}
